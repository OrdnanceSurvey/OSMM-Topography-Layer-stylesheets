FME workspace cartographicsymbol_addattributes.fmw

BulkAttributeRenamer
    ATTRCHOICE = All Attributes
    CASE_CHANGE_TYPE = lower
    MODE_CHOICE = RENAME
    PATTERN_ACTION_DISP = CASECHANGE
    -> cartographicsymbol
cartographicsymbol: AttributeCreator
    ATTR_TABLE:
      SET_TO style_code = FME_CONDITIONAL:DEFAULT_VALUE'99'BOOL_OP;OR;COMPOSITE_TEST;<Unused>;TEST @Value(featurecode) = 10091'1'BOOL_OP;OR;COMPOSITE_TEST;<Unused>;TEST @Value(featurecode) = 10082'2'BOOL_OP;OR;COMPOSITE_TEST;<Unused>;TEST @Value(featurecode) = 10130'3'BOOL_OP;OR;COMPOSITE_TEST;<Unused>;TEST @Value(featurecode) = 10066;TEST @Value(featurecode) = 10170'4'BOOL_OP;OR;COMPOSITE_TEST;<Unused>;TEST @Value(featurecode) = 10165'5'BOOL_OP;OR;COMPOSITE_TEST;<Unused>;TEST @Value(featurecode) = 10177'6'FME_NUM_CONDITIONS7___
      SET_TO style_description = FME_CONDITIONAL:DEFAULT_VALUE'Unclassified'BOOL_OP;OR;COMPOSITE_TEST;<Unused>;TEST @Value(featurecode) = 10091'Culvert Symbol'BOOL_OP;OR;COMPOSITE_TEST;<Unused>;TEST @Value(featurecode) = 10082'Direction Of Flow Symbol'BOOL_OP;OR;COMPOSITE_TEST;<Unused>;TEST @Value(featurecode) = 10130'Boundary Half Mereing Symbol'BOOL_OP;OR;COMPOSITE_TEST;<Unused>;TEST @Value(featurecode) = 10066;TEST @Value(featurecode) = 10170'Bench Mark Symbol'BOOL_OP;OR;COMPOSITE_TEST;<Unused>;TEST @Value(featurecode) = 10165'Railway Switch Symbol'BOOL_OP;OR;COMPOSITE_TEST;<Unused>;TEST @Value(featurecode) = 10177'Road Related Flow Symbol'FME_NUM_CONDITIONS7___
