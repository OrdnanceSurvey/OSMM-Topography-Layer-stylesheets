FME workspace cartographictext_addattributes.fmw

BulkAttributeRenamer
    ATTRCHOICE = All Attributes
    CASE_CHANGE_TYPE = lower
    MODE_CHOICE = RENAME
    PATTERN_ACTION_DISP = CASECHANGE
    -> cartographictext
cartographictext: AttributeCreator
    ATTR_TABLE:
      SET_TO style_description = FME_CONDITIONAL:DEFAULT_VALUE'Unclassified'BOOL_OP;OR;COMPOSITE_TEST;<Unused>;TEST @Value(descriptivegroup) CONTAINS Buildings Or Structure'Building Text'BOOL_OP;OR;COMPOSITE_TEST;<Unused>;TEST @Value(descriptivegroup) CONTAINS Inland Water'Water Text'BOOL_OP;OR;COMPOSITE_TEST;<Unused>;TEST @Value(descriptivegroup) CONTAINS Road Or Track'Road Text'BOOL_OP;OR;COMPOSITE_TEST;<Unused>;TEST @Value(descriptivegroup) = Terrain And Height'Height Text'BOOL_OP;OR;COMPOSITE_TEST;<Unused>;TEST @Value(descriptivegroup) CONTAINS Roadside'Roadside Text'BOOL_OP;OR;COMPOSITE_TEST;<Unused>;TEST @Value(descriptivegroup) CONTAINS Structure'Structure Text'BOOL_OP;OR;COMPOSITE_TEST;<Unused>;TEST @Value(descriptivegroup) = Political Or Administrative'Administrative Text'BOOL_OP;AND;COMPOSITE_TEST;<Unused>;TEST @Value(descriptivegroup) = General Surface;TEST @Value(make) = Natural'General Surface Natural Text'BOOL_OP;COMPOSITE;COMPOSITE_TEST;(1 AND 2) OR (3 AND 4);TEST @Value(descriptivegroup) = General Surface;TEST @Value(make) = Manmade;TEST @Value(descriptivegroup) = General Surface;TEST make ATTRIBUTE_VALUE_NULL _FME_BLANK_STRING_'General Surface Manmade Text'BOOL_OP;AND;COMPOSITE_TEST;<Unused>;TEST @Value(descriptivegroup) = Landform;TEST @Value(make) = Natural'Landform Natural Text'BOOL_OP;AND;COMPOSITE_TEST;<Unused>;TEST @Value(descriptiveterm) = Foreshore'Foreshore Text'BOOL_OP;AND;COMPOSITE_TEST;<Unused>;TEST @Value(descriptivegroup) CONTAINS Tidal Water'Tidal Water Text'BOOL_OP;AND;COMPOSITE_TEST;<Unused>;TEST @Value(descriptiveterm) = Built Environment'Built Environment Text'BOOL_OP;AND;COMPOSITE_TEST;<Unused>;TEST @Value(descriptiveterm) CONTAINS Historic Interest'Historic Text'BOOL_OP;AND;COMPOSITE_TEST;<Unused>;TEST @Value(descriptiveterm) = Rail'Rail Text'BOOL_OP;AND;COMPOSITE_TEST;<Unused>;TEST @Value(descriptiveterm) CONTAINS General Feature'General Feature Text'BOOL_OP;AND;COMPOSITE_TEST;<Unused>;TEST @Value(descriptivegroup) = Landform;TEST @Value(make) = Manmade'Landform Manmade Text'FME_NUM_CONDITIONS18___
      SET_TO style_code = FME_CONDITIONAL:DEFAULT_VALUE'99'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'3'BOOL_OP;OR;COMPOSITE_TEST;<Unused>;TEST @Value(descriptivegroup) = Terrain And Height'4'BOOL_OP;OR;COMPOSITE_TEST;<Unused>;TEST @Value(descriptivegroup) CONTAINS Roadside'5'BOOL_OP;OR;COMPOSITE_TEST;<Unused>;TEST @Value(descriptivegroup) CONTAINS Structure'6'BOOL_OP;OR;COMPOSITE_TEST;<Unused>;TEST @Value(descriptivegroup) = Political Or Administrative'7'BOOL_OP;AND;COMPOSITE_TEST;<Unused>;TEST @Value(descriptivegroup) = General Surface;TEST @Value(make) = Natural'8'BOOL_OP;COMPOSITE;COMPOSITE_TEST;(1 AND 2) OR (3 AND 4);TEST @Value(descriptivegroup) = General Surface;TEST @Value(make) = Manmade;TEST @Value(descriptivegroup) = General Surface;TEST make ATTRIBUTE_VALUE_NULL _FME_BLANK_STRING_'9'BOOL_OP;AND;COMPOSITE_TEST;<Unused>;TEST @Value(descriptivegroup) = Landform;TEST @Value(make) = Natural'10'BOOL_OP;AND;COMPOSITE_TEST;<Unused>;TEST @Value(descriptiveterm) = Foreshore'11'BOOL_OP;AND;COMPOSITE_TEST;<Unused>;TEST @Value(descriptivegroup) CONTAINS Tidal Water'12'BOOL_OP;AND;COMPOSITE_TEST;<Unused>;TEST @Value(descriptiveterm) = Built Environment'13'BOOL_OP;AND;COMPOSITE_TEST;<Unused>;TEST @Value(descriptiveterm) CONTAINS Historic Interest'14'BOOL_OP;AND;COMPOSITE_TEST;<Unused>;TEST @Value(descriptiveterm) = Rail'15'BOOL_OP;AND;COMPOSITE_TEST;<Unused>;TEST @Value(descriptiveterm) CONTAINS General Feature'16'BOOL_OP;AND;COMPOSITE_TEST;<Unused>;TEST @Value(descriptivegroup) = Landform;TEST @Value(make) = Manmade'17'FME_NUM_CONDITIONS18___
      SET_TO colour_code = FME_CONDITIONAL:DEFAULT_VALUE'1'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'1'BOOL_OP;OR;COMPOSITE_TEST;<Unused>;TEST @Value(descriptivegroup) = Terrain And Height'3'BOOL_OP;OR;COMPOSITE_TEST;<Unused>;TEST @Value(descriptivegroup) CONTAINS Roadside'1'BOOL_OP;OR;COMPOSITE_TEST;<Unused>;TEST @Value(descriptivegroup) CONTAINS Structure'1'BOOL_OP;OR;COMPOSITE_TEST;<Unused>;TEST @Value(descriptivegroup) = Political Or Administrative'5'BOOL_OP;AND;COMPOSITE_TEST;<Unused>;TEST @Value(descriptivegroup) = General Surface;TEST @Value(make) = Natural'1'BOOL_OP;COMPOSITE;COMPOSITE_TEST;(1 AND 2) OR (3 AND 4);TEST @Value(descriptivegroup) = General Surface;TEST @Value(make) = Manmade;TEST @Value(descriptivegroup) = General Surface;TEST make ATTRIBUTE_VALUE_NULL _FME_BLANK_STRING_'1'BOOL_OP;AND;COMPOSITE_TEST;<Unused>;TEST @Value(descriptivegroup) = Landform;TEST @Value(make) = Natural'4'BOOL_OP;AND;COMPOSITE_TEST;<Unused>;TEST @Value(descriptiveterm) = Foreshore'4'BOOL_OP;AND;COMPOSITE_TEST;<Unused>;TEST @Value(descriptivegroup) CONTAINS Tidal Water'2'BOOL_OP;AND;COMPOSITE_TEST;<Unused>;TEST @Value(descriptiveterm) = Built Environment'1'BOOL_OP;AND;COMPOSITE_TEST;<Unused>;TEST @Value(descriptiveterm) CONTAINS Historic Interest'1'BOOL_OP;AND;COMPOSITE_TEST;<Unused>;TEST @Value(descriptiveterm) = Rail'1'BOOL_OP;AND;COMPOSITE_TEST;<Unused>;TEST @Value(descriptiveterm) CONTAINS General Feature'1'BOOL_OP;AND;COMPOSITE_TEST;<Unused>;TEST @Value(descriptivegroup) = Landform;TEST @Value(make) = Manmade'4'FME_NUM_CONDITIONS18___
      SET_TO font_code = FME_CONDITIONAL:DEFAULT_VALUE'1'BOOL_OP;OR;COMPOSITE_TEST;<Unused>;TEST @Value(descriptivegroup) CONTAINS Buildings Or Structure'1'BOOL_OP;OR;COMPOSITE_TEST;<Unused>;TEST @Value(descriptivegroup) CONTAINS Inland Water'2'BOOL_OP;OR;COMPOSITE_TEST;<Unused>;TEST @Value(descriptivegroup) CONTAINS Road Or Track'1'BOOL_OP;OR;COMPOSITE_TEST;<Unused>;TEST @Value(descriptivegroup) = Terrain And Height'1'BOOL_OP;OR;COMPOSITE_TEST;<Unused>;TEST @Value(descriptivegroup) CONTAINS Roadside'1'BOOL_OP;OR;COMPOSITE_TEST;<Unused>;TEST @Value(descriptivegroup) CONTAINS Structure'1'BOOL_OP;OR;COMPOSITE_TEST;<Unused>;TEST @Value(descriptivegroup) = Political Or Administrative'1'BOOL_OP;AND;COMPOSITE_TEST;<Unused>;TEST @Value(descriptivegroup) = General Surface;TEST @Value(make) = Natural'1'BOOL_OP;COMPOSITE;COMPOSITE_TEST;(1 AND 2) OR (3 AND 4);TEST @Value(descriptivegroup) = General Surface;TEST @Value(make) = Manmade;TEST @Value(descriptivegroup) = General Surface;TEST make ATTRIBUTE_VALUE_NULL _FME_BLANK_STRING_'1'BOOL_OP;AND;COMPOSITE_TEST;<Unused>;TEST @Value(descriptivegroup) = Landform;TEST @Value(make) = Natural'1'BOOL_OP;AND;COMPOSITE_TEST;<Unused>;TEST @Value(descriptiveterm) = Foreshore'1'BOOL_OP;AND;COMPOSITE_TEST;<Unused>;TEST @Value(descriptivegroup) CONTAINS Tidal Water'2'BOOL_OP;AND;COMPOSITE_TEST;<Unused>;TEST @Value(descriptiveterm) = Built Environment'1'BOOL_OP;AND;COMPOSITE_TEST;<Unused>;TEST @Value(descriptiveterm) CONTAINS Historic Interest'3'BOOL_OP;AND;COMPOSITE_TEST;<Unused>;TEST @Value(descriptiveterm) = Rail'1'BOOL_OP;AND;COMPOSITE_TEST;<Unused>;TEST @Value(descriptiveterm) CONTAINS General Feature'1'BOOL_OP;AND;COMPOSITE_TEST;<Unused>;TEST @Value(descriptivegroup) = Landform;TEST @Value(make) = Manmade'1'FME_NUM_CONDITIONS18___
      SET_TO rotation = @div(@Value(orientation),10)
      SET_TO geo_x = FME_CONDITIONAL:DEFAULT_VALUE'_FME_NO_OP_'BOOL_OP;OR;COMPOSITE_TEST;<Unused>;TEST @Value(anchorposition) = 0'0'BOOL_OP;OR;COMPOSITE_TEST;<Unused>;TEST @Value(anchorposition) = 1'0'BOOL_OP;OR;COMPOSITE_TEST;<Unused>;TEST @Value(anchorposition) = 2'0'BOOL_OP;OR;COMPOSITE_TEST;<Unused>;TEST @Value(anchorposition) = 3'0.5'BOOL_OP;OR;COMPOSITE_TEST;<Unused>;TEST @Value(anchorposition) = 4'0.5'BOOL_OP;OR;COMPOSITE_TEST;<Unused>;TEST @Value(anchorposition) = 5'0.5'BOOL_OP;OR;COMPOSITE_TEST;<Unused>;TEST @Value(anchorposition) = 6'1'BOOL_OP;OR;COMPOSITE_TEST;<Unused>;TEST @Value(anchorposition) = 7'1'BOOL_OP;OR;COMPOSITE_TEST;<Unused>;TEST @Value(anchorposition) = 8'1'FME_NUM_CONDITIONS10___
      SET_TO geo_y = FME_CONDITIONAL:DEFAULT_VALUE'_FME_NO_OP_'BOOL_OP;OR;COMPOSITE_TEST;<Unused>;TEST @Value(anchorposition) = 0'0'BOOL_OP;OR;COMPOSITE_TEST;<Unused>;TEST @Value(anchorposition) = 1'0.5'BOOL_OP;OR;COMPOSITE_TEST;<Unused>;TEST @Value(anchorposition) = 2'1'BOOL_OP;OR;COMPOSITE_TEST;<Unused>;TEST @Value(anchorposition) = 3'0'BOOL_OP;OR;COMPOSITE_TEST;<Unused>;TEST @Value(anchorposition) = 4'0.5'BOOL_OP;OR;COMPOSITE_TEST;<Unused>;TEST @Value(anchorposition) = 5'1'BOOL_OP;OR;COMPOSITE_TEST;<Unused>;TEST @Value(anchorposition) = 6'0'BOOL_OP;OR;COMPOSITE_TEST;<Unused>;TEST @Value(anchorposition) = 7'0.5'BOOL_OP;OR;COMPOSITE_TEST;<Unused>;TEST @Value(anchorposition) = 8'1'FME_NUM_CONDITIONS10___
      SET_TO anchor = FME_CONDITIONAL:DEFAULT_VALUE'_FME_NO_OP_'BOOL_OP;OR;COMPOSITE_TEST;<Unused>;TEST @Value(anchorposition) = 0'SW'BOOL_OP;OR;COMPOSITE_TEST;<Unused>;TEST @Value(anchorposition) = 1'W'BOOL_OP;OR;COMPOSITE_TEST;<Unused>;TEST @Value(anchorposition) = 2'NW'BOOL_OP;OR;COMPOSITE_TEST;<Unused>;TEST @Value(anchorposition) = 3'S'BOOL_OP;OR;COMPOSITE_TEST;<Unused>;TEST @Value(anchorposition) = 4''BOOL_OP;OR;COMPOSITE_TEST;<Unused>;TEST @Value(anchorposition) = 5'N'BOOL_OP;OR;COMPOSITE_TEST;<Unused>;TEST @Value(anchorposition) = 6'SE'BOOL_OP;OR;COMPOSITE_TEST;<Unused>;TEST @Value(anchorposition) = 7'E'BOOL_OP;OR;COMPOSITE_TEST;<Unused>;TEST @Value(anchorposition) = 8'NE'FME_NUM_CONDITIONS10___
