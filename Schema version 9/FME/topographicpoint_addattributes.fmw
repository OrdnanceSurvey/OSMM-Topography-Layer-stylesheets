FME workspace topographicpoint_addattributes.fmw

BulkAttributeRenamer
    ATTRCHOICE = All Attributes
    CASE_CHANGE_TYPE = lower
    MODE_CHOICE = RENAME
    PATTERN_ACTION_DISP = CASECHANGE
    -> topographicpoint
topographicpoint: AttributeCreator
    ATTR_TABLE:
      SET_TO style_code = FME_CONDITIONAL:DEFAULT_VALUE'99'BOOL_OP;OR;COMPOSITE_TEST;<Unused>;TEST @Value(descriptiveterm) = Spot Height'1'BOOL_OP;OR;COMPOSITE_TEST;<Unused>;TEST @Value(descriptiveterm) = Emergency Telephone'2'BOOL_OP;OR;COMPOSITE_TEST;<Unused>;TEST @Value(descriptiveterm) CONTAINS Site Of Heritage'3'BOOL_OP;OR;COMPOSITE_TEST;<Unused>;TEST @Value(descriptiveterm) CONTAINS Culvert'4'BOOL_OP;OR;COMPOSITE_TEST;<Unused>;TEST @Value(descriptiveterm) = Positioned Nonconiferous Tree'5'BOOL_OP;OR;COMPOSITE_TEST;<Unused>;TEST @Value(descriptiveterm) CONTAINS Inland Water'6'BOOL_OP;OR;COMPOSITE_TEST;<Unused>;TEST @Value(descriptiveterm) CONTAINS Roadside'7'BOOL_OP;OR;COMPOSITE_TEST;<Unused>;TEST @Value(descriptiveterm) CONTAINS Overhead Construction'8'BOOL_OP;OR;COMPOSITE_TEST;<Unused>;TEST @Value(descriptiveterm) CONTAINS Rail'9'BOOL_OP;OR;COMPOSITE_TEST;<Unused>;TEST @Value(descriptiveterm) = Positioned Coniferous Tree'10'BOOL_OP;OR;COMPOSITE_TEST;<Unused>;TEST @Value(descriptiveterm) = Boundary Post Or Stone'11'BOOL_OP;OR;COMPOSITE_TEST;<Unused>;TEST @Value(descriptiveterm) = Triangulation Point Or Pillar'12'BOOL_OP;OR;COMPOSITE_TEST;<Unused>;TEST @Value(descriptiveterm) = Historic Interest'13'BOOL_OP;OR;COMPOSITE_TEST;<Unused>;TEST @Value(descriptiveterm) = Landform;TEST @Value(descriptiveterm) = Positioned Boulder'14'BOOL_OP;OR;COMPOSITE_TEST;<Unused>;TEST @Value(descriptiveterm) CONTAINS Tidal Water'15'BOOL_OP;OR;COMPOSITE_TEST;<Unused>;TEST @Value(descriptiveterm) CONTAINS Structure'16'FME_NUM_CONDITIONS17___
      SET_TO style_description = FME_CONDITIONAL:DEFAULT_VALUE'Unclassified'BOOL_OP;OR;COMPOSITE_TEST;<Unused>;TEST @Value(descriptiveterm) = Spot Height'Spot Height Point'BOOL_OP;OR;COMPOSITE_TEST;<Unused>;TEST @Value(descriptiveterm) = Emergency Telephone'Emergency Telephone Point'BOOL_OP;OR;COMPOSITE_TEST;<Unused>;TEST @Value(descriptiveterm) CONTAINS Site Of Heritage'Site Of Heritage Point'BOOL_OP;OR;COMPOSITE_TEST;<Unused>;TEST @Value(descriptiveterm) CONTAINS Culvert'Culvert Point'BOOL_OP;OR;COMPOSITE_TEST;<Unused>;TEST @Value(descriptiveterm) = Positioned Nonconiferous Tree'Positioned Nonconiferous Tree Point'BOOL_OP;OR;COMPOSITE_TEST;<Unused>;TEST @Value(descriptiveterm) CONTAINS Inland Water'Inland Water Point'BOOL_OP;OR;COMPOSITE_TEST;<Unused>;TEST @Value(descriptiveterm) CONTAINS Roadside'Roadside Point'BOOL_OP;OR;COMPOSITE_TEST;<Unused>;TEST @Value(descriptiveterm) CONTAINS Overhead Construction'Overhead Construction Point'BOOL_OP;OR;COMPOSITE_TEST;<Unused>;TEST @Value(descriptiveterm) CONTAINS Rail'Rail Point'BOOL_OP;OR;COMPOSITE_TEST;<Unused>;TEST @Value(descriptiveterm) = Positioned Coniferous Tree'Positioned Coniferous Tree Point'BOOL_OP;OR;COMPOSITE_TEST;<Unused>;TEST @Value(descriptiveterm) = Boundary Post Or Stone'Boundary Post Point'BOOL_OP;OR;COMPOSITE_TEST;<Unused>;TEST @Value(descriptiveterm) = Triangulation Point Or Pillar'Triangulation Point Or Pillar Point'BOOL_OP;OR;COMPOSITE_TEST;<Unused>;TEST @Value(descriptiveterm) = Historic Interest'Historic Point'BOOL_OP;OR;COMPOSITE_TEST;<Unused>;TEST @Value(descriptiveterm) = Landform;TEST @Value(descriptiveterm) = Positioned Boulder'Landform Point'BOOL_OP;OR;COMPOSITE_TEST;<Unused>;TEST @Value(descriptiveterm) CONTAINS Tidal Water'Tidal Water Point'BOOL_OP;OR;COMPOSITE_TEST;<Unused>;TEST @Value(descriptiveterm) CONTAINS Structure'Structure Point'FME_NUM_CONDITIONS17___
