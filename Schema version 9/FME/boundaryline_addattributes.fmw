FME workspace boundaryline_addattributes.fmw

BulkAttributeRenamer
    ATTRCHOICE = All Attributes
    CASE_CHANGE_TYPE = lower
    MODE_CHOICE = RENAME
    PATTERN_ACTION_DISP = CASECHANGE
    -> boundaryline
boundaryline: AttributeCreator
    ATTR_TABLE:
      SET_TO style_code = FME_CONDITIONAL:DEFAULT_VALUE'99'BOOL_OP;OR;COMPOSITE_TEST;<Unused>;TEST @Value(featurecode) = 10136'1'BOOL_OP;OR;COMPOSITE_TEST;<Unused>;TEST @Value(featurecode) = 10131'2'BOOL_OP;OR;COMPOSITE_TEST;<Unused>;TEST @Value(featurecode) = 10128'3'BOOL_OP;OR;COMPOSITE_TEST;<Unused>;TEST @Value(featurecode) = 10127'4'BOOL_OP;OR;COMPOSITE_TEST;<Unused>;TEST @Value(featurecode) = 10135'5'FME_NUM_CONDITIONS6___
      SET_TO style_description = FME_CONDITIONAL:DEFAULT_VALUE'Unclassified'BOOL_OP;OR;COMPOSITE_TEST;<Unused>;TEST @Value(featurecode) = 10136'Parish Boundary'BOOL_OP;OR;COMPOSITE_TEST;<Unused>;TEST @Value(featurecode) = 10131'District Boundary'BOOL_OP;OR;COMPOSITE_TEST;<Unused>;TEST @Value(featurecode) = 10128'Electoral Boundary'BOOL_OP;OR;COMPOSITE_TEST;<Unused>;TEST @Value(featurecode) = 10127'County Boundary'BOOL_OP;OR;COMPOSITE_TEST;<Unused>;TEST @Value(featurecode) = 10135'Parliamentary Boundary'FME_NUM_CONDITIONS6___
