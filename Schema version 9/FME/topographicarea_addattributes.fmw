FME workspace topographicarea_addattributes.fmw

BulkAttributeRenamer
    ATTRCHOICE = All Attributes
    CASE_CHANGE_TYPE = lower
    MODE_CHOICE = RENAME
    PATTERN_ACTION_DISP = CASECHANGE
    -> topographicarea
topographicarea: AttributeCreator
    ATTR_TABLE:
      SET_TO style_code = FME_CONDITIONAL:DEFAULT_VALUE'99'BOOL_OP;OR;COMPOSITE_TEST;<Unused>;TEST @Value(descriptiveterm) = Multi Surface'1'BOOL_OP;OR;COMPOSITE_TEST;<Unused>;TEST @Value(descriptiveterm) = Archway'2'BOOL_OP;COMPOSITE;COMPOSITE_TEST;1 AND (2 OR 3);TEST @Value(descriptiveterm) = Bridge;TEST @Value(descriptivegroup) CONTAINS Road Or Track;TEST @Value(descriptivegroup) CONTAINS Roadside'3'BOOL_OP;AND;COMPOSITE_TEST;<Unused>;TEST @Value(descriptiveterm) = Bridge;TEST @Value(descriptivegroup) CONTAINS Rail'4'BOOL_OP;OR;COMPOSITE_TEST;<Unused>;TEST @Value(descriptiveterm) = Bridge'5'BOOL_OP;OR;COMPOSITE_TEST;<Unused>;TEST @Value(descriptiveterm) CONTAINS Level Crossing'6'BOOL_OP;OR;COMPOSITE_TEST;<Unused>;TEST @Value(descriptiveterm) = Traffic Calming'7'BOOL_OP;OR;COMPOSITE_TEST;<Unused>;TEST @Value(descriptiveterm) = Pylon'8'BOOL_OP;OR;COMPOSITE_TEST;<Unused>;TEST @Value(descriptiveterm) = Track'9'BOOL_OP;OR;COMPOSITE_TEST;<Unused>;TEST @Value(descriptiveterm) = Step'10'BOOL_OP;OR;COMPOSITE_TEST;<Unused>;TEST @Value(descriptiveterm) CONTAINS Canal'11'BOOL_OP;OR;COMPOSITE_TEST;<Unused>;TEST @Value(descriptiveterm) CONTAINS Footbridge'12'BOOL_OP;COMPOSITE;COMPOSITE_TEST;(1 OR 2) AND (3 OR 4);TEST @Value(descriptiveterm) CONTAINS Nonconiferous Trees;TEST @Value(descriptiveterm) CONTAINS Nonconiferous Trees (Scattered);TEST @Value(descriptiveterm) CONTAINS Coniferous Trees;TEST @Value(descriptiveterm) CONTAINS Coniferous Trees (Scattered)'13'BOOL_OP;OR;COMPOSITE_TEST;<Unused>;TEST @Value(descriptiveterm) CONTAINS Nonconiferous Trees;TEST @Value(descriptiveterm) CONTAINS Nonconiferous Trees (Scattered)'14'BOOL_OP;OR;COMPOSITE_TEST;<Unused>;TEST @Value(descriptiveterm) CONTAINS Coniferous Trees;TEST @Value(descriptiveterm) CONTAINS Coniferous Trees (Scattered)'15'BOOL_OP;OR;COMPOSITE_TEST;<Unused>;TEST @Value(descriptiveterm) CONTAINS Agricultural Land'16'BOOL_OP;OR;COMPOSITE_TEST;<Unused>;TEST @Value(descriptiveterm) CONTAINS Orchard'17'BOOL_OP;OR;COMPOSITE_TEST;<Unused>;TEST @Value(descriptiveterm) CONTAINS Coppice Or Osiers'18'BOOL_OP;OR;COMPOSITE_TEST;<Unused>;TEST @Value(descriptiveterm) CONTAINS Scrub'19'BOOL_OP;OR;COMPOSITE_TEST;<Unused>;TEST @Value(descriptiveterm) CONTAINS Boulders;TEST @Value(descriptiveterm) CONTAINS Boulders (Scattered)'20'BOOL_OP;OR;COMPOSITE_TEST;<Unused>;TEST @Value(descriptiveterm) CONTAINS Boulders;TEST @Value(descriptiveterm) CONTAINS Rock (Scattered)'21'BOOL_OP;OR;COMPOSITE_TEST;<Unused>;TEST @Value(descriptiveterm) CONTAINS Scree'22'BOOL_OP;OR;COMPOSITE_TEST;<Unused>;TEST @Value(descriptiveterm) CONTAINS Rough Grassland'23'BOOL_OP;OR;COMPOSITE_TEST;<Unused>;TEST @Value(descriptiveterm) CONTAINS Heath'24'BOOL_OP;OR;COMPOSITE_TEST;<Unused>;TEST @Value(descriptiveterm) CONTAINS Marsh Reeds Or Saltmarsh;TEST @Value(descriptiveterm) CONTAINS Saltmarsh'25'BOOL_OP;OR;COMPOSITE_TEST;<Unused>;TEST @Value(descriptiveterm) CONTAINS Sand'26'BOOL_OP;OR;COMPOSITE_TEST;<Unused>;TEST @Value(descriptiveterm) CONTAINS Mud'27'BOOL_OP;OR;COMPOSITE_TEST;<Unused>;TEST @Value(descriptiveterm) CONTAINS Shingle'28'BOOL_OP;OR;COMPOSITE_TEST;<Unused>;TEST @Value(descriptiveterm) CONTAINS Marsh'29'BOOL_OP;OR;COMPOSITE_TEST;<Unused>;TEST @Value(descriptiveterm) CONTAINS Reeds'30'BOOL_OP;OR;COMPOSITE_TEST;<Unused>;TEST @Value(descriptiveterm) CONTAINS Foreshore'31'BOOL_OP;OR;COMPOSITE_TEST;<Unused>;TEST @Value(descriptiveterm) = Slope'32'BOOL_OP;OR;COMPOSITE_TEST;<Unused>;TEST @Value(descriptiveterm) = Cliff'33'BOOL_OP;OR;COMPOSITE_TEST;<Unused>;TEST @Value(descriptivegroup) CONTAINS Building'34'BOOL_OP;AND;COMPOSITE_TEST;<Unused>;TEST @Value(descriptivegroup) CONTAINS General Surface;TEST @Value(make) = Natural'35'BOOL_OP;COMPOSITE;COMPOSITE_TEST;1 AND (2 OR 3);TEST @Value(descriptivegroup) CONTAINS General Surface;TEST @Value(make) = Manmade;TEST @Value(make) = Unknown'36'BOOL_OP;AND;COMPOSITE_TEST;<Unused>;TEST @Value(descriptivegroup) CONTAINS Road Or Track;TEST @Value(make) = Manmade'37'BOOL_OP;AND;COMPOSITE_TEST;<Unused>;TEST @Value(descriptivegroup) CONTAINS Roadside;TEST @Value(make) = Natural'38'BOOL_OP;COMPOSITE;COMPOSITE_TEST;1 AND (2 OR 3);TEST @Value(descriptivegroup) CONTAINS Roadside;TEST @Value(make) = Manmade;TEST @Value(make) = Unknown'39'BOOL_OP;OR;COMPOSITE_TEST;<Unused>;TEST @Value(descriptivegroup) CONTAINS Inland Water'40'BOOL_OP;OR;COMPOSITE_TEST;<Unused>;TEST @Value(descriptivegroup) CONTAINS Path'41'BOOL_OP;COMPOSITE;COMPOSITE_TEST;1 AND (2 OR 3);TEST @Value(descriptivegroup) CONTAINS Rail;TEST @Value(make) = Manmade;TEST @Value(make) = Unknown'42'BOOL_OP;AND;COMPOSITE_TEST;<Unused>;TEST @Value(descriptivegroup) LIKE Rail;TEST @Value(make) = Natural'43'BOOL_OP;OR;COMPOSITE_TEST;<Unused>;TEST @Value(descriptivegroup) CONTAINS Structure'44'BOOL_OP;OR;COMPOSITE_TEST;<Unused>;TEST @Value(descriptivegroup) = Glasshouse'45'BOOL_OP;AND;COMPOSITE_TEST;<Unused>;TEST @Value(descriptivegroup) CONTAINS Landform;TEST @Value(make) = Natural'46'BOOL_OP;AND;COMPOSITE_TEST;<Unused>;TEST @Value(descriptivegroup) LIKE Tidal Water'47'BOOL_OP;AND;COMPOSITE_TEST;<Unused>;TEST @Value(descriptivegroup) CONTAINS Landform;TEST @Value(make) = Manmade'48'FME_NUM_CONDITIONS49___
      SET_TO style_description = FME_CONDITIONAL:DEFAULT_VALUE'Unclassified'BOOL_OP;OR;COMPOSITE_TEST;<Unused>;TEST @Value(descriptiveterm) = Multi Surface'Multi Surface Fill'BOOL_OP;OR;COMPOSITE_TEST;<Unused>;TEST @Value(descriptiveterm) = Archway'Archway Fill'BOOL_OP;COMPOSITE;COMPOSITE_TEST;1 AND (2 OR 3);TEST @Value(descriptiveterm) = Bridge;TEST @Value(descriptivegroup) CONTAINS Road Or Track;TEST @Value(descriptivegroup) CONTAINS Roadside'Road Bridge Fill'BOOL_OP;AND;COMPOSITE_TEST;<Unused>;TEST @Value(descriptiveterm) = Bridge;TEST @Value(descriptivegroup) CONTAINS Rail'Rail Bridge Fill'BOOL_OP;OR;COMPOSITE_TEST;<Unused>;TEST @Value(descriptiveterm) = Bridge'Bridge Fill'BOOL_OP;OR;COMPOSITE_TEST;<Unused>;TEST @Value(descriptiveterm) CONTAINS Level Crossing'Level Crossing Fill'BOOL_OP;OR;COMPOSITE_TEST;<Unused>;TEST @Value(descriptiveterm) = Traffic Calming'Traffic Calming Fill'BOOL_OP;OR;COMPOSITE_TEST;<Unused>;TEST @Value(descriptiveterm) = Pylon'Pylon Fill'BOOL_OP;OR;COMPOSITE_TEST;<Unused>;TEST @Value(descriptiveterm) = Track'Track Fill'BOOL_OP;OR;COMPOSITE_TEST;<Unused>;TEST @Value(descriptiveterm) = Step'Step Fill'BOOL_OP;OR;COMPOSITE_TEST;<Unused>;TEST @Value(descriptiveterm) CONTAINS Canal'Canal Fill'BOOL_OP;OR;COMPOSITE_TEST;<Unused>;TEST @Value(descriptiveterm) CONTAINS Footbridge'Footbridge Fill'BOOL_OP;COMPOSITE;COMPOSITE_TEST;(1 OR 2) AND (3 OR 4);TEST @Value(descriptiveterm) CONTAINS Nonconiferous Trees;TEST @Value(descriptiveterm) CONTAINS Nonconiferous Trees (Scattered);TEST @Value(descriptiveterm) CONTAINS Coniferous Trees;TEST @Value(descriptiveterm) CONTAINS Coniferous Trees (Scattered)'Mixed Woodland Fill'BOOL_OP;OR;COMPOSITE_TEST;<Unused>;TEST @Value(descriptiveterm) CONTAINS Nonconiferous Trees;TEST @Value(descriptiveterm) CONTAINS Nonconiferous Trees (Scattered)'Nonconiferous Tree Fill'BOOL_OP;OR;COMPOSITE_TEST;<Unused>;TEST @Value(descriptiveterm) CONTAINS Coniferous Trees;TEST @Value(descriptiveterm) CONTAINS Coniferous Trees (Scattered)'Coniferous Tree Fill'BOOL_OP;OR;COMPOSITE_TEST;<Unused>;TEST @Value(descriptiveterm) CONTAINS Agricultural Land'Agricultural Land Fill'BOOL_OP;OR;COMPOSITE_TEST;<Unused>;TEST @Value(descriptiveterm) CONTAINS Orchard'Orchard Fill'BOOL_OP;OR;COMPOSITE_TEST;<Unused>;TEST @Value(descriptiveterm) CONTAINS Coppice Or Osiers'Coppice Or Osiers Fill'BOOL_OP;OR;COMPOSITE_TEST;<Unused>;TEST @Value(descriptiveterm) CONTAINS Scrub'Scrub Fill'BOOL_OP;OR;COMPOSITE_TEST;<Unused>;TEST @Value(descriptiveterm) CONTAINS Boulders;TEST @Value(descriptiveterm) CONTAINS Boulders (Scattered)'Boulders Fill'BOOL_OP;OR;COMPOSITE_TEST;<Unused>;TEST @Value(descriptiveterm) CONTAINS Boulders;TEST @Value(descriptiveterm) CONTAINS Rock (Scattered)'Rock Fill'BOOL_OP;OR;COMPOSITE_TEST;<Unused>;TEST @Value(descriptiveterm) CONTAINS Scree'Scree Fill'BOOL_OP;OR;COMPOSITE_TEST;<Unused>;TEST @Value(descriptiveterm) CONTAINS Rough Grassland'Rough Grassland Fill'BOOL_OP;OR;COMPOSITE_TEST;<Unused>;TEST @Value(descriptiveterm) CONTAINS Heath'Heath Fill'BOOL_OP;OR;COMPOSITE_TEST;<Unused>;TEST @Value(descriptiveterm) CONTAINS Marsh Reeds Or Saltmarsh;TEST @Value(descriptiveterm) CONTAINS Saltmarsh'Saltmarsh Fill'BOOL_OP;OR;COMPOSITE_TEST;<Unused>;TEST @Value(descriptiveterm) CONTAINS Sand'Sand Fill'BOOL_OP;OR;COMPOSITE_TEST;<Unused>;TEST @Value(descriptiveterm) CONTAINS Mud'Mud Fill'BOOL_OP;OR;COMPOSITE_TEST;<Unused>;TEST @Value(descriptiveterm) CONTAINS Shingle'Shingle Fill'BOOL_OP;OR;COMPOSITE_TEST;<Unused>;TEST @Value(descriptiveterm) CONTAINS Marsh'Marsh Fill'BOOL_OP;OR;COMPOSITE_TEST;<Unused>;TEST @Value(descriptiveterm) CONTAINS Reeds'Reeds Fill'BOOL_OP;OR;COMPOSITE_TEST;<Unused>;TEST @Value(descriptiveterm) CONTAINS Foreshore'Foreshore Fill'BOOL_OP;OR;COMPOSITE_TEST;<Unused>;TEST @Value(descriptiveterm) = Slope'Slope Fill'BOOL_OP;OR;COMPOSITE_TEST;<Unused>;TEST @Value(descriptiveterm) = Cliff'Cliff Fill'BOOL_OP;OR;COMPOSITE_TEST;<Unused>;TEST @Value(descriptivegroup) CONTAINS Building'Building Fill'BOOL_OP;AND;COMPOSITE_TEST;<Unused>;TEST @Value(descriptivegroup) CONTAINS General Surface;TEST @Value(make) = Natural'Natural Fill'BOOL_OP;COMPOSITE;COMPOSITE_TEST;1 AND (2 OR 3);TEST @Value(descriptivegroup) CONTAINS General Surface;TEST @Value(make) = Manmade;TEST @Value(make) = Unknown'Manmade Fill'BOOL_OP;AND;COMPOSITE_TEST;<Unused>;TEST @Value(descriptivegroup) CONTAINS Road Or Track;TEST @Value(make) = Manmade'Road Or Track Fill'BOOL_OP;AND;COMPOSITE_TEST;<Unused>;TEST @Value(descriptivegroup) CONTAINS Roadside;TEST @Value(make) = Natural'Roadside Natural Fill'BOOL_OP;COMPOSITE;COMPOSITE_TEST;1 AND (2 OR 3);TEST @Value(descriptivegroup) CONTAINS Roadside;TEST @Value(make) = Manmade;TEST @Value(make) = Unknown'Roadside Manmade Fill'BOOL_OP;OR;COMPOSITE_TEST;<Unused>;TEST @Value(descriptivegroup) CONTAINS Inland Water'Inland Water Fill'BOOL_OP;OR;COMPOSITE_TEST;<Unused>;TEST @Value(descriptivegroup) CONTAINS Path'Path Fill'BOOL_OP;COMPOSITE;COMPOSITE_TEST;1 AND (2 OR 3);TEST @Value(descriptivegroup) CONTAINS Rail;TEST @Value(make) = Manmade;TEST @Value(make) = Unknown'Rail Manmade Fill'BOOL_OP;AND;COMPOSITE_TEST;<Unused>;TEST @Value(descriptivegroup) LIKE Rail;TEST @Value(make) = Natural'Rail Natural Fill'BOOL_OP;OR;COMPOSITE_TEST;<Unused>;TEST @Value(descriptivegroup) CONTAINS Structure'Structure Fill'BOOL_OP;OR;COMPOSITE_TEST;<Unused>;TEST @Value(descriptivegroup) = Glasshouse'Glasshouse Fill'BOOL_OP;AND;COMPOSITE_TEST;<Unused>;TEST @Value(descriptivegroup) CONTAINS Landform;TEST @Value(make) = Natural'Landform Natural Fill'BOOL_OP;AND;COMPOSITE_TEST;<Unused>;TEST @Value(descriptivegroup) LIKE Tidal Water'Tidal Water Fill'BOOL_OP;AND;COMPOSITE_TEST;<Unused>;TEST @Value(descriptivegroup) CONTAINS Landform;TEST @Value(make) = Manmade'Landform Manmade Fill'FME_NUM_CONDITIONS49___
