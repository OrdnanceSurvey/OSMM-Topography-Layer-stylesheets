FME workspace topographicline_addattributes.fmw

BulkAttributeRenamer
    ATTRCHOICE = All Attributes
    CASE_CHANGE_TYPE = lower
    MODE_CHOICE = RENAME
    PATTERN_ACTION_DISP = CASECHANGE
    -> topographicline
topographicline: AttributeCreator
    ATTR_TABLE:
      SET_TO style_code = FME_CONDITIONAL:DEFAULT_VALUE'99'BOOL_OP;OR;COMPOSITE_TEST;<Unused>;TEST @Value(descriptiveterm) = Polygon Closing Link'1'BOOL_OP;OR;COMPOSITE_TEST;<Unused>;TEST @Value(descriptiveterm) = Inferred Property Closing Link'2'BOOL_OP;OR;COMPOSITE_TEST;<Unused>;TEST @Value(descriptiveterm) = Bottom Of Slope'3'BOOL_OP;OR;COMPOSITE_TEST;<Unused>;TEST @Value(descriptiveterm) = Top Of Slope'4'BOOL_OP;OR;COMPOSITE_TEST;<Unused>;TEST @Value(descriptiveterm) = Step'5'BOOL_OP;OR;COMPOSITE_TEST;<Unused>;TEST @Value(descriptiveterm) CONTAINS Mean High Water (Springs)'6'BOOL_OP;OR;COMPOSITE_TEST;<Unused>;TEST @Value(descriptiveterm) = Traffic Calming'7'BOOL_OP;OR;COMPOSITE_TEST;<Unused>;TEST @Value(descriptiveterm) = Standard Gauge Track'8'BOOL_OP;OR;COMPOSITE_TEST;<Unused>;TEST @Value(descriptiveterm) = Bottom Of Cliff'9'BOOL_OP;OR;COMPOSITE_TEST;<Unused>;TEST @Value(descriptiveterm) = Top Of Cliff'10'BOOL_OP;OR;COMPOSITE_TEST;<Unused>;TEST @Value(descriptiveterm) = Mean Low Water (Springs)'11'BOOL_OP;OR;COMPOSITE_TEST;<Unused>;TEST @Value(descriptiveterm) = Unmade Path Alignment'12'BOOL_OP;OR;COMPOSITE_TEST;<Unused>;TEST @Value(descriptiveterm) CONTAINS Overhead Construction'13'BOOL_OP;OR;COMPOSITE_TEST;<Unused>;TEST @Value(descriptiveterm) = Culvert'14'BOOL_OP;OR;COMPOSITE_TEST;<Unused>;TEST @Value(descriptiveterm) = Pylon'15'BOOL_OP;OR;COMPOSITE_TEST;<Unused>;TEST @Value(descriptiveterm) = Ridge Or Rock Line'16'BOOL_OP;OR;COMPOSITE_TEST;<Unused>;TEST @Value(descriptiveterm) = Narrow Gauge'17'BOOL_OP;OR;COMPOSITE_TEST;<Unused>;TEST @Value(descriptiveterm) = Buffer'18'BOOL_OP;OR;COMPOSITE_TEST;<Unused>;TEST @Value(descriptiveterm) = Tunnel Edge'19'BOOL_OP;OR;COMPOSITE_TEST;<Unused>;TEST @Value(descriptiveterm) CONTAINS Line Of Posts'20'BOOL_OP;OR;COMPOSITE_TEST;<Unused>;TEST @Value(descriptiveterm) = Drain'21'BOOL_OP;OR;COMPOSITE_TEST;<Unused>;TEST @Value(descriptiveterm) CONTAINS Normal Tidal Limit'22'BOOL_OP;AND;COMPOSITE_TEST;<Unused>;TEST @Value(descriptivegroup) CONTAINS General Feature;TEST @Value(physicalpresence) != Edge / Limit'23'BOOL_OP;AND;COMPOSITE_TEST;<Unused>;TEST @Value(descriptivegroup) CONTAINS Building;TEST @Value(descriptiveterm) = Outline;TEST @Value(physicalpresence) = Obstructing'24'BOOL_OP;AND;COMPOSITE_TEST;<Unused>;TEST @Value(descriptivegroup) CONTAINS General Feature;TEST @Value(physicalpresence) = Edge / Limit'25'BOOL_OP;AND;COMPOSITE_TEST;<Unused>;TEST @Value(descriptivegroup) CONTAINS Road Or Track'26'BOOL_OP;AND;COMPOSITE_TEST;<Unused>;TEST @Value(descriptivegroup) CONTAINS Building;TEST @Value(descriptiveterm) = Division;TEST @Value(physicalpresence) = Obstructing'27'BOOL_OP;AND;COMPOSITE_TEST;<Unused>;TEST @Value(descriptivegroup) CONTAINS Inland Water'28'BOOL_OP;AND;COMPOSITE_TEST;<Unused>;TEST @Value(descriptivegroup) CONTAINS General Surface;TEST @Value(make) = Natural'29'BOOL_OP;AND;COMPOSITE_TEST;<Unused>;TEST @Value(descriptivegroup) CONTAINS Building;TEST @Value(descriptiveterm) = Outline;TEST @Value(physicalpresence) = Overhead'30'BOOL_OP;AND;COMPOSITE_TEST;<Unused>;TEST @Value(descriptivegroup) = Landform;TEST @Value(make) = Natural'31'BOOL_OP;AND;COMPOSITE_TEST;<Unused>;TEST @Value(descriptivegroup) = Historic Interest'32'BOOL_OP;AND;COMPOSITE_TEST;<Unused>;TEST @Value(descriptivegroup) = Landform;TEST @Value(make) = Manmade'33'FME_NUM_CONDITIONS34___
      SET_TO style_description = FME_CONDITIONAL:DEFAULT_VALUE'Unclassified'BOOL_OP;OR;COMPOSITE_TEST;<Unused>;TEST @Value(descriptiveterm) = Polygon Closing Link'Polygon Closing Line'BOOL_OP;OR;COMPOSITE_TEST;<Unused>;TEST @Value(descriptiveterm) = Inferred Property Closing Link'Property Closing Line'BOOL_OP;OR;COMPOSITE_TEST;<Unused>;TEST @Value(descriptiveterm) = Bottom Of Slope'Bottom Of Slope Line'BOOL_OP;OR;COMPOSITE_TEST;<Unused>;TEST @Value(descriptiveterm) = Top Of Slope'Top Of Slope Line'BOOL_OP;OR;COMPOSITE_TEST;<Unused>;TEST @Value(descriptiveterm) = Step'Step Line'BOOL_OP;OR;COMPOSITE_TEST;<Unused>;TEST @Value(descriptiveterm) CONTAINS Mean High Water (Springs)'Mean High Water Line'BOOL_OP;OR;COMPOSITE_TEST;<Unused>;TEST @Value(descriptiveterm) = Traffic Calming'Traffic Calming Line'BOOL_OP;OR;COMPOSITE_TEST;<Unused>;TEST @Value(descriptiveterm) = Standard Gauge Track'Standard Gauge Track Line'BOOL_OP;OR;COMPOSITE_TEST;<Unused>;TEST @Value(descriptiveterm) = Bottom Of Cliff'Bottom Of Cliff Line'BOOL_OP;OR;COMPOSITE_TEST;<Unused>;TEST @Value(descriptiveterm) = Top Of Cliff'Top Of Cliff Line'BOOL_OP;OR;COMPOSITE_TEST;<Unused>;TEST @Value(descriptiveterm) = Mean Low Water (Springs)'Mean Low Water Line'BOOL_OP;OR;COMPOSITE_TEST;<Unused>;TEST @Value(descriptiveterm) = Unmade Path Alignment'Path Line'BOOL_OP;OR;COMPOSITE_TEST;<Unused>;TEST @Value(descriptiveterm) CONTAINS Overhead Construction'Overhead Construction Line'BOOL_OP;OR;COMPOSITE_TEST;<Unused>;TEST @Value(descriptiveterm) = Culvert'Culvert Line'BOOL_OP;OR;COMPOSITE_TEST;<Unused>;TEST @Value(descriptiveterm) = Pylon'Pylon Line'BOOL_OP;OR;COMPOSITE_TEST;<Unused>;TEST @Value(descriptiveterm) = Ridge Or Rock Line'Ridge Or Rock Line'BOOL_OP;OR;COMPOSITE_TEST;<Unused>;TEST @Value(descriptiveterm) = Narrow Gauge'Narrow Gauge Line'BOOL_OP;OR;COMPOSITE_TEST;<Unused>;TEST @Value(descriptiveterm) = Buffer'Railway Buffer Line'BOOL_OP;OR;COMPOSITE_TEST;<Unused>;TEST @Value(descriptiveterm) = Tunnel Edge'Tunnel Edge Line'BOOL_OP;OR;COMPOSITE_TEST;<Unused>;TEST @Value(descriptiveterm) CONTAINS Line Of Posts'Line Of Posts Line'BOOL_OP;OR;COMPOSITE_TEST;<Unused>;TEST @Value(descriptiveterm) = Drain'Drain Line'BOOL_OP;OR;COMPOSITE_TEST;<Unused>;TEST @Value(descriptiveterm) CONTAINS Normal Tidal Limit'Normal Tidal Limit Line'BOOL_OP;AND;COMPOSITE_TEST;<Unused>;TEST @Value(descriptivegroup) CONTAINS General Feature;TEST @Value(physicalpresence) != Edge / Limit'Default Line'BOOL_OP;AND;COMPOSITE_TEST;<Unused>;TEST @Value(descriptivegroup) CONTAINS Building;TEST @Value(descriptiveterm) = Outline;TEST @Value(physicalpresence) = Obstructing'Building Outline Line'BOOL_OP;AND;COMPOSITE_TEST;<Unused>;TEST @Value(descriptivegroup) CONTAINS General Feature;TEST @Value(physicalpresence) = Edge / Limit'Edge Line'BOOL_OP;AND;COMPOSITE_TEST;<Unused>;TEST @Value(descriptivegroup) CONTAINS Road Or Track'Road Or Track Line'BOOL_OP;AND;COMPOSITE_TEST;<Unused>;TEST @Value(descriptivegroup) CONTAINS Building;TEST @Value(descriptiveterm) = Division;TEST @Value(physicalpresence) = Obstructing'Building Division Line'BOOL_OP;AND;COMPOSITE_TEST;<Unused>;TEST @Value(descriptivegroup) CONTAINS Inland Water'Inland Water Line'BOOL_OP;AND;COMPOSITE_TEST;<Unused>;TEST @Value(descriptivegroup) CONTAINS General Surface;TEST @Value(make) = Natural'General Surface Natural Line'BOOL_OP;AND;COMPOSITE_TEST;<Unused>;TEST @Value(descriptivegroup) CONTAINS Building;TEST @Value(descriptiveterm) = Outline;TEST @Value(physicalpresence) = Overhead'Building Overhead Line'BOOL_OP;AND;COMPOSITE_TEST;<Unused>;TEST @Value(descriptivegroup) = Landform;TEST @Value(make) = Natural'Landform Natural Line'BOOL_OP;AND;COMPOSITE_TEST;<Unused>;TEST @Value(descriptivegroup) = Historic Interest'Historic Interest Line'BOOL_OP;AND;COMPOSITE_TEST;<Unused>;TEST @Value(descriptivegroup) = Landform;TEST @Value(make) = Manmade'Landform Manmade Line'FME_NUM_CONDITIONS34___
